FME workspace sample_script_fmeserver_old_params.fmw

Parameters:
- Perimeter = POLYGON((6.5838791192197 46.5044344288519,6.5838791192197 46.6025470130881,6.72082104901253 46.6025470130881,6.72082104901253 46.5044344288519))   # Polygone d'export (au format WKT) 
- Product = a049fecb-30d9-9124-ed41-068b566a0855   # Identifiant du produit 
- FolderOut = D:\Temp\FME_test\OUTPUT   # Répertoire de sortie 
- Parameters = {"FORMAT" : "SHP","SELECTION" : "PASS_THROUGH","PROJECTION" : "SWITZERLAND95"}   # Liste dynamique de paramètres au format json
- INPUT_GDB = D:\Temp\FME_test\GDB_INPUT\ASIT-VD.gdb   # Géodatabase Esri Source 

Readers:
- GEODATABASE_FILE_1: GEODATABASE_FILE from $(INPUT_GDB)

Writers:
- GEODATABASE_FILE_2: GEODATABASE_FILE to $(FolderOut)
- ESRISHAPE_1: ESRISHAPE to $(FolderOut)

Products (reader GEODATABASE_FILE_1)
    attributes: OBJECTID integer, guid char(8000), fc char(8000)
    -> Tester
Tester
    BOOL_OP = OR
    TEST_MODE = Automatic
    TEST_DESCRIPTION = ""
    TEST_CLAUSE = TEST @Value(guid) = $(Product)
    PASSED -> ListBuilder
ListBuilder
    LIST_NAME = list_fc
    -> ListConcatenator
ListConcatenator
    LIST_ATTR = list_fc{}.fc
    SEP = " "
    DROP_EMPTY_PARTS = Yes
    VAL_ATTR = feature_type_to_read
    -> FeatureReader [INITIATOR]
Note: Output [GEODATABASE_FILE]
FeatureClass1 (writer GEODATABASE_FILE_2)
Note: Output [ESRISHAPE]
Shapefile1 (writer ESRISHAPE_1)

Bookmark: Lecture des classes d'entités à extraire
FeatureReader
    FORMAT = GEODATABASE_FILE
    GEODATABASE_FILE_SPLIT_COMPLEX_EDGES = no
    GEODATABASE_FILE_IGNORE_NETWORK_INFO = yes
    GEODATABASE_FILE_SPLIT_COMPLEX_ANNOS = no
    GEODATABASE_FILE_SEARCH_ORDER = SPATIAL_FIRST
    GEODATABASE_FILE_CHECK_SIMPLE_GEOM = no
    DATASET = D:\Temp\FME_test\GDB_INPUT\ASIT-VD.gdb
    GEODATABASE_FILE_IGNORE_RELATIONSHIP_INFO = yes
    INTERACT = <No Spatial Filter>
    GEODATABASE_FILE_USE_SEARCH_ENVELOPE = NO
    GEODATABASE_FILE_QUERY_FEATURE_TYPES_FOR_MERGE_FILTERS = Yes
    GEODATABASE_FILE_TABLELIST = Products
    GEODATABASE_FILE_MERGE_FEAT_LINKED_ANNOS = no
    COMBINE_GEOM = Use Result
    GEODATABASE_FILE_SEARCH_METHOD = GEODB_INTERSECTS
    GEODATABASE_FILE_SPLIT_MULTI_PART_ANNOS = no
    ATTR_ACCUM_MODE = Only Use Result
    FEATURETYPES = @Value(feature_type_to_read)
    GEODATABASE_FILE_RESOLVE_DOMAINS = no
    GEODATABASE_FILE_ALIAS_MODE = NONE
    GEODATABASE_FILE_CLIP_TO_ENVELOPE = NO
    GEODATABASE_FILE_RESOLVE_SUBTYPE_NAMES = yes
    GEODATABASE_FILE_TRANSLATE_SPATIAL_DATA_ONLY = no
    OUTPUT_FEATURES_DISPLAY = Schema and Data Features
    GEODATABASE_FILE_FEATURE_READ_MODE = Features
    GEODATABASE_FILE_CACHE_MULTIPATCH_TEXTURES = yes
    ATTRIBUTES = DGMR_TPR_RC_ARRDT,"OBJECTID,ARRDT,Shape_Length,Shape_Area",LAD_TPR_CANTON,"OBJECTID,SIGLE_CANT,NO_CANTON,NOM_LANG_O,NOM_LANG_1,NOM_FRANCA,NOM_MAJ,NOM_MIN,NO_CHEF_LI,PERIMETRE,SURFACE,Shape_Length,Shape_Area",LAD_TPR_COMMUNE,"OBJECTID,NO_COM_FED,NO_COM_CAN,NOM_MAJ,NOM_MIN,N_A_MAJ_15,N_A_MIN_15,NO_DIS_CAN,NO_DIS_FED,NO_CANTON,NO_SECTEUR,NOM_MAJ_OF,NOM_MIN_OF,NOM_MAJ_15,NOM_MIN_15,PERIMETRE,SURFACE,Shape_Length,Shape_Area",LAD_TPR_DISTRICT,"OBJECTID,NO_DIS_FED,NO_DIS_CAN,NOM_MAJ,NOM_MIN,CODE,CODE_AUTO,NO_CANTON,NOM_COMPL_,NOM_COMPL1,PERIMETRE,SURFACE,Shape_Length,Shape_Area",OAJE_TPR_INST_ACC,"OBJECTID,NOM,PLAGE_OUVE,ADRESSE,NPA,LOCALITE,RESEAU,TELEPHONE,FORME_JURI,PLAGE_AGE,CAPACITE_T",OAJE_TPR_RESEAU_ACC,"OBJECTID,RESEAU,URL,Shape_Length,Shape_Area",Products,"OBJECTID,guid,fc",SFFN_TPR_ARR_FORESTIER,"OBJECTID,NO_ARR_FOR,NOM_ARR_FO,Shape_Length,Shape_Area",SFFN_TPR_CIRC_FAUNE,"OBJECTID,NO_CIRC_FA,NOM_CIRC_F,Shape_Length,Shape_Area",SFFN_TPR_CIRC_PECHE,"OBJECTID,NO_CIRC_PE,NOM_CIRC_P,Shape_Length,Shape_Area"
    <SCHEMA> -> Shapefile1 (writer ESRISHAPE_1)
    <SCHEMA> -> FeatureClass1 (writer GEODATABASE_FILE_2)
    <OTHER> -> SpatialFilter [Candidate]

Bookmark: Génération du périmètre d'export à partir de [Perimeter] en format WKT
Creator
    NUM = 1
    GEOMTYPE = Geometry Object
    CREATED -> GeometryReplacer
GeometryReplacer
    SOURCE = $(Perimeter)
    KIND_LONG = OGC Well Known Text
    REMOVE_ATTRIBUTE = Yes
    OGC_WKT_PRECISION_DISPLAY = 64-bit
    -> Reprojection_WGS84_MN95
Reprojection_WGS84_MN95: Reprojector
    SOURCE = EPSG:4326
    DEST = EPSG:2056
    INTERPOLATION_TYPE_NAME = Nearest Neighbor
    RASTER_CELL_SIZE = Preserve Cells
    REPROJECTED -> SpatialFilter [Filter]

Bookmark: Transformations utilisant les paramètres récupérés précédemment
SpatialFilter
    PREDATTR = _predicate
    PASS_CRITERIA = Pass Against One Filter
    ATTR_CONFLICT_RES = Use Candidate
    CURVE_BOUNDARY_RULE_PARAM = Default Rule
    BASE_TYPE = Multiple Filters
    PREDICATES = INTERSECTS
    AGGREGATE_HANDLING = Yes
    ATTR_ACCUM_MODE = Merge Filter
    USE_BOUNDING_BOX = No
    PASSED -> VariableRetriever
VariableRetriever
    VARNAME = PROJECTION_EPSG
    VALUE_ATTR = PROJECTION_EPSG
    SCOPE = Global
    -> VariableRetriever_3
VariableRetriever_3
    VARNAME = PROJECTION_NOM
    VALUE_ATTR = PROJECTION_NOM
    SCOPE = Global
    -> VariableRetriever_2
VariableRetriever_2
    VARNAME = FORMAT
    VALUE_ATTR = FORMAT
    SCOPE = Global
    -> Reprojector
Reprojector
    SOURCE = Read from feature
    DEST = @Value(PROJECTION_EPSG)
    INTERPOLATION_TYPE_NAME = Nearest Neighbor
    RASTER_CELL_SIZE = Preserve Cells
    REPROJECTED -> AttributeFilter
AttributeFilter
    ATTR_NAME = FORMAT
    ATTR_VALUES = <EMPTY>,<MISSING>,<NULL>,<UNFILTERED>,GDB,SHP
    GDB -> FeatureClass1 (writer GEODATABASE_FILE_2)
    SHP -> Shapefile1 (writer ESRISHAPE_1)

Bookmark: Récupération des paramètres du workbench à partir de la liste générique de [Parameters] au format json
Creator_2
    NUM = 1
    GEOMTYPE = Geometry Object
    CREATED -> JSONFlattener
JSONFlattener
    ERROR_LIST_ATTR = _json_error
    RECURSIVE = Yes
    NEW_ATTRIBUTES = json_FORMAT json_SELECTION json_PROJECTION
    PREFIX_STRING = json_
    JSON_DOCUMENT = $(Parameters)
    -> Parameter_format
Parameter_format: VariableSetter
    VARNAME = FORMAT
    VALUE = @Value(json_FORMAT)
    SCOPE = Global
    -> Parameter_format_2
Parameter_format_2: VariableSetter
    VARNAME = SELECTION
    VALUE = @Value(json_SELECTION)
    SCOPE = Global
    -> Parameter_projection
Parameter_projection: VariableSetter
    VARNAME = PROJECTION_EPSG
    VALUE = FME_CONDITIONAL:DEFAULT_VALUE'@Abort(No valid projection defined)'BOOL_OP;OR;COMPOSITE_TEST;<Unused>;TEST @Value(json_PROJECTION) = SWITZERLAND'EPSG:21781'BOOL_OP;OR;COMPOSITE_TEST;<Unused>;TEST @Value(json_PROJECTION) = SWITZERLAND95'EPSG:2056'FME_NUM_CONDITIONS3___
    SCOPE = Global
    -> Parameter_projection_2
Parameter_projection_2: VariableSetter
    VARNAME = PROJECTION_NOM
    VALUE = FME_CONDITIONAL:DEFAULT_VALUE'@Abort(No valid projection defined)'BOOL_OP;OR;COMPOSITE_TEST;<Unused>;TEST @Value(json_PROJECTION) = SWITZERLAND'MN03'BOOL_OP;OR;COMPOSITE_TEST;<Unused>;TEST @Value(json_PROJECTION) = SWITZERLAND95'MN95'FME_NUM_CONDITIONS3___
    SCOPE = Global
