FME workspace sample_script_fmeserver.fmw

Parameters:
- Perimeter = POLYGON((6.295363612819898 46.32659377501397,6.288481575413728 46.65130021757865,7.055293317619941 46.656470518789625,7.057591178865101 46.33173342736276,6.295363612819898 46.32659377501397))   # Polygone d'export (au format WKT) 
- Product = 6f5afa6b-7f0a-ec54-a9a7-44f004d6edda   # Identifiant du produit 
- FolderOut = C:\Temp\extract\orders\20acf36a-58c6-49d2-ad5b-b27fa1457b91\output   # Répertoire de sortie 
- Parameters = {"FORMAT":"SHP","PROJECTION":"SWITZERLAND","SELECTION":"PASS_THROUGH","GROUPMENT":"YES","RAISON":"AVARIE","Communes":"","REMARK":"Parcelle N°3658 à Clarens \u0022Montreux\u0022"}   # Liste dynamique de paramètres au format json
- SourceDataset_FILEGDB = .\ASIT-VD.gdb   # File Geodatabase
- OrderLabel = 259547   # Libellé de la commande 
- Request = 365   # Identifiant de la requête 
- Client = 2edc1a50-4837-4c44-1519-3ebc85f14588   # Identifiant du client 
- Organism = 4a142a5d-16bf-84d4-111f-57d76c834493   # Identifiant de l'organisme 
- INPUT_GDB = $(FME_MF_DIR)ASIT-VD.gdb   # Géodatabase Esri Source 

Readers:
- GEODATABASE_FILE_1: GEODATABASE_FILE from $(INPUT_GDB)
- FILEGDB_1: FILEGDB from $(SourceDataset_FILEGDB)

Writers:
- ESRISHAPE_1: ESRISHAPE to $(FolderOut)
- FILEGDB_2: FILEGDB to $(FolderOut)\output

Products (reader GEODATABASE_FILE_1) [off]
    attributes: OBJECTID integer, guid char(8000), fc char(8000)
    -> Tester
Products (reader FILEGDB_1)
    attributes: OBJECTID objectid, guid text(8000), fc text(8000)
    -> Tester
Tester
    TEST_MODE = Automatic
    BOOL_OP = OR
    TEST_DESCRIPTION = ""
    TEST_CLAUSE = TEST @Value(guid) = $(Product)
    PASSED -> ListBuilder
ListBuilder
    LIST_NAME = list_fc
    -> ListConcatenator
ListConcatenator
    VAL_ATTR = feature_type_to_read
    SEP = " "
    LIST_ATTR = list_fc{}.fc
    DROP_EMPTY_PARTS = Yes
    -> FeatureReader [INITIATOR]
Note: Output : OUTPUT [FILEGDB]
Products (writer FILEGDB_2)
Note: Output [ESRISHAPE]
Shapefile1 (writer ESRISHAPE_1)
VariableRetriever_4
    SCOPE = Global
    VALUE_ATTR = REMARK
    VARNAME = REMARK
    -> Logger
Logger
    MAXFEATS = 20
    MESSAGE = Remark is: @Value(REMARK)
    MAXCOORDS = 20

Bookmark: Lecture des classes d'entités à extraire
FeatureReader
    FORMAT = FILEGDB
    FILEGDB_QUERY_FEATURE_TYPES_FOR_MERGE_FILTERS = Yes
    DATASET = $(INPUT_GDB)
    FILEGDB_CLIP_TO_ENVELOPE = NO
    FEATURETYPES = @Value(feature_type_to_read)
    ATTR_ACCUM_MODE = Only Use Result
    OUTPUT_FEATURES_DISPLAY = Schema and Data Features
    INTERACT = <No Spatial Filter>
    FILEGDB_USE_SEARCH_ENVELOPE = NO
    COMBINE_GEOM = Use Result
    ATTRIBUTES = DGMR_TPR_RC_ARRDT,"OBJECTID,ARRDT,Shape_Length,Shape_Area",LAD_TPR_CANTON,"OBJECTID,SIGLE_CANT,NO_CANTON,NOM_LANG_O,NOM_LANG_1,NOM_FRANCA,NOM_MAJ,NOM_MIN,NO_CHEF_LI,PERIMETRE,SURFACE,Shape_Length,Shape_Area",LAD_TPR_COMMUNE,"OBJECTID,NO_COM_FED,NO_COM_CAN,NOM_MAJ,NOM_MIN,N_A_MAJ_15,N_A_MIN_15,NO_DIS_CAN,NO_DIS_FED,NO_CANTON,NO_SECTEUR,NOM_MAJ_OF,NOM_MIN_OF,NOM_MAJ_15,NOM_MIN_15,PERIMETRE,SURFACE,Shape_Length,Shape_Area",LAD_TPR_DISTRICT,"OBJECTID,NO_DIS_FED,NO_DIS_CAN,NOM_MAJ,NOM_MIN,CODE,CODE_AUTO,NO_CANTON,NOM_COMPL_,NOM_COMPL1,PERIMETRE,SURFACE,Shape_Length,Shape_Area",OAJE_TPR_INST_ACC,"OBJECTID,NOM,PLAGE_OUVE,ADRESSE,NPA,LOCALITE,RESEAU,TELEPHONE,FORME_JURI,PLAGE_AGE,CAPACITE_T",OAJE_TPR_RESEAU_ACC,"OBJECTID,RESEAU,URL,Shape_Length,Shape_Area",Products,"OBJECTID,guid,fc",SFFN_TPR_ARR_FORESTIER,"OBJECTID,NO_ARR_FOR,NOM_ARR_FO,Shape_Length,Shape_Area",SFFN_TPR_CIRC_FAUNE,"OBJECTID,NO_CIRC_FA,NOM_CIRC_F,Shape_Length,Shape_Area",SFFN_TPR_CIRC_PECHE,"OBJECTID,NO_CIRC_PE,NOM_CIRC_P,Shape_Length,Shape_Area"
    <SCHEMA> -> Shapefile1 (writer ESRISHAPE_1)
    <SCHEMA> -> Products (writer FILEGDB_2)
    <OTHER> -> SpatialFilter [Candidate]

Bookmark: Génération du périmètre d'export à partir de [Perimeter] en format WKT
Creator
    NUM = 1
    GEOMTYPE = Geometry Object
    CREATED -> GeometryReplacer
GeometryReplacer
    OGC_WKT_PRECISION_DISPLAY = 64-bit
    SOURCE = $(Perimeter)
    REMOVE_ATTRIBUTE = Yes
    KIND_LONG = OGC Well Known Text
    -> Reprojection_WGS84_MN95
Reprojection_WGS84_MN95: Reprojector
    RASTER_CELL_SIZE = Preserve Cells
    SOURCE = EPSG:4326
    DEST = EPSG:2056
    INTERPOLATION_TYPE_NAME = Nearest Neighbor
    REPROJECTED -> SpatialFilter [Filter]

Bookmark: Transformations utilisant les paramètres récupérés précédemment
SpatialFilter
    CURVE_BOUNDARY_RULE_PARAM = Default Rule
    PREDICATES = INTERSECTS
    ATTR_ACCUM_MODE = Merge Filter
    PASS_CRITERIA = Pass Against One Filter
    ATTR_CONFLICT_RES = Use Candidate
    USE_BOUNDING_BOX = No
    AGGREGATE_HANDLING = Yes
    PREDATTR = _predicate
    BASE_TYPE = Multiple Filters
    PASSED -> VariableRetriever
VariableRetriever
    SCOPE = Global
    VALUE_ATTR = PROJECTION_EPSG
    VARNAME = PROJECTION_EPSG
    -> VariableRetriever_3
VariableRetriever_3
    SCOPE = Global
    VALUE_ATTR = PROJECTION_NOM
    VARNAME = PROJECTION_NOM
    -> VariableRetriever_2
VariableRetriever_2
    SCOPE = Global
    VALUE_ATTR = FORMAT
    VARNAME = FORMAT
    -> Reprojector
Reprojector
    RASTER_CELL_SIZE = Preserve Cells
    SOURCE = Read from feature
    DEST = @Value(PROJECTION_EPSG)
    INTERPOLATION_TYPE_NAME = Nearest Neighbor
    REPROJECTED -> AttributeFilter
AttributeFilter
    ATTR_NAME = FORMAT
    ATTR_VALUES = <EMPTY>,<MISSING>,<NULL>,<UNFILTERED>,GDB,SHP
    GDB -> GeometryFilter
    SHP -> Shapefile1 (writer ESRISHAPE_1)

Bookmark: Cas des multipoints
GeometryFilter
    GEOM_PORT_NAMES = Point
    BREAK_AGG = No
    POINT -> Deaggregator
    <UNFILTERED> -> Products (writer FILEGDB_2)
Deaggregator
    SPLIT_COMPOSITES = No
    LIST_ATTR_MODE_LOOKUP = LEAN
    PART_NUMBER_FIELD = _part_number
    MODE = Flatten One Level
    GEOM_NAME_FIELD = _geometry_name
    EXPLODE_INSTANCES = No
    DEAGGREGATED -> Products (writer FILEGDB_2)

Bookmark: Récupération des paramètres du workbench à partir de la liste générique de [Parameters] au format json
Creator_2
    NUM = 1
    GEOMTYPE = Geometry Object
    CREATED -> JSONFlattener
JSONFlattener
    PREFIX_STRING = json_
    JSON_DOCUMENT = $(Parameters)
    RECURSIVE = Yes
    NEW_ATTRIBUTES = json_FORMAT json_SELECTION json_PROJECTION json_REMARK
    ERROR_LIST_ATTR = _json_error
    -> Parameter_format
Parameter_format: VariableSetter
    SCOPE = Global
    VARNAME = FORMAT
    VALUE = @Value(json_FORMAT)
    -> Parameter_format_2
Parameter_format_2: VariableSetter
    SCOPE = Global
    VARNAME = SELECTION
    VALUE = @Value(json_SELECTION)
    -> Parameter_projection
Parameter_projection: VariableSetter
    SCOPE = Global
    VARNAME = PROJECTION_EPSG
    VALUE = FME_CONDITIONAL:DEFAULT_VALUE'@Abort(No valid projection defined)'BOOL_OP;OR;COMPOSITE_TEST;<Unused>;TEST @Value(json_PROJECTION) = SWITZERLAND'EPSG:21781'BOOL_OP;OR;COMPOSITE_TEST;<Unused>;TEST @Value(json_PROJECTION) = SWITZERLAND95'EPSG:2056'FME_NUM_CONDITIONS3___
    -> Parameter_projection_2
Parameter_projection_2: VariableSetter
    SCOPE = Global
    VARNAME = PROJECTION_NOM
    VALUE = FME_CONDITIONAL:DEFAULT_VALUE'@Abort(No valid projection defined)'BOOL_OP;OR;COMPOSITE_TEST;<Unused>;TEST @Value(json_PROJECTION) = SWITZERLAND'MN03'BOOL_OP;OR;COMPOSITE_TEST;<Unused>;TEST @Value(json_PROJECTION) = SWITZERLAND95'MN95'FME_NUM_CONDITIONS3___
    -> Parameter_format_3
Parameter_format_3: VariableSetter
    SCOPE = Global
    VARNAME = REMARK
    VALUE = @Value(json_REMARK)
    -> VariableRetriever_4
